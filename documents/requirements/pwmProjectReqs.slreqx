# pwmProjectReqs

## buttons: Pushbuttons (Container)

### buttons_1: Quantity of pushbuttons (Informational)
There should be five buttons in the project

### buttons_3: Functions of the pushbuttons (Container)

#### buttons_3_1: Function of N button (Informational)
Duty cycles must increase when N button is pressed

#### buttons_3_2: Function of S button (Informational)
Duty cycles must decrease when S button is pressed

#### buttons_3_3: Function of C button (Informational)
Duty cycles must set to zero when C button is pressed

#### buttons_3_4: Function of N button (Informational)
Next channel must be selected when N button is pressed

#### buttons_3_5: Function of E button (Informational)
Previous channel must be selected when N button is pressed

### buttons_2: Placement of the pushbuttons on the panel (Informational)
Buttons should be placed on the panel as follows:
N
W C E
S

### buttons_4: Simultaneous buttonstrokes (Functional)
When several buttons are pressed, system must not respond

### buttons_5: Single buttonstroke (Functional)
When one button is pressed, system must respond

## filter: Button digital filter (Container)
Operation description
Digital filter is used in order to filter out the glitches associated with switch transitions (debouncing).

### filter_1: FIlter period (Functional)
Module must filter out the glitches with duration less than 1 ms

## pressing_mode_handler: Pressing mode handler (Container)
Operation description
Single quick pressing of N (S) button lead to increasing (decreasing) by one current duty cycle. Holding N (S) button, after determinated period of time duty cucle must increase (decrease) automaticaly with determinated frequency

### pressing_mode_handler_1: Pause duration (Functional)
Pause between single-pressing and continuous-pressing modes must be equal to 1 second

### pressing_mode_handler_2: Continuous-pressing mode frequency (Functional)
Continuous-pressing mode frequency must be equal to 0.1 second

## pwm: PWM generator (Container)

### pwm_1: PWM (Functional)
Bit capacity of PWM must be changed from 5 to 10 bits. Default value equals to 5 bits.

### pwm_2: Quantity of channels (Informational)
There should be three independent PWM channels

### pwm_3: PWM types (Functional)
Three PWM types must be implemented:
1. Trailing edge modulation (back);
2. Leading edge modulation (front);
3. Centered pulses

### pwm_4: Synchrosignal (Functional)
Module must generate synchrosignal for PWM channels

### pwm_5: PWM frequency (Functional)
PWM frequency must be parameter. Default value equals to 1 kHz

## #30: Justifications

### #31

### #32

### #33

### #34
